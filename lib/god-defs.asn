God { }

DEFINITIONS IMPLICIT TAGS ::=

BEGIN

God ::= SEQUENCE {
	header 					Header,
	metadataGlobal	Metadata OPTIONAL,
	metric					Metric,
	union						Union
}

-- header 

Version ::= INTEGER

Header ::= SEQUENCE {
	version					Version,
	comment					UTF8String
}

-- metadata

Metadata ::= SET OF MetadataEntry

MetadataEntry ::= SEQUENCE {
	name						UTF8String,
	value						UTF8String
}

-- metric

Metric ::= SEQUENCE {
	parameterDim		INTEGER,
	criteriaDim			INTEGER,
	setsCount				INTEGER
}

-- data

Union ::= SEQUENCE OF Set

Set ::= SEQUENCE {
	setMetadata			Metadata OPTIONAL,
	pointCount			INTEGER,
	points					Points
}

Points ::= SEQUENCE OF Point

Point ::= SEQUENCE {
	parameters			SEQUENCE OF REAL,
	criteria				SEQUENCE OF REAL
}

END
